FME workspace suelosCA.fmw

Parameters:
- SourceDataset_GEODATABASE_FILE = $(FME_MF_DIR)LagoValencia.gdb   # File Geodatabase
- FEATURE_TYPES = mapa_suelo_regven
- SourceDataset_GEODATABASE_FILE_5 = $(FME_MF_DIR)LagoValencia.gdb   # File Geodatabase
- FEATURE_TYPES_2 = UCPOTENC
- SourceDataset_GEODATABASE_FILE_4 = $(FME_MF_DIR)LagoValencia.gdb   # File Geodatabase
- FEATURE_TYPES_3 = UCATRIBU
- DestDataset_GEODATABASE_FILE = $(FME_MF_DIR)LagoValencia.gdb   # File Geodatabase

Readers:
- NULL_1: NULL
- GEODATABASE_FILE_1: GEODATABASE_FILE from $(SourceDataset_GEODATABASE_FILE)
- GEODATABASE_FILE_2: GEODATABASE_FILE from $(SourceDataset_GEODATABASE_FILE_5)
- GEODATABASE_FILE_3: GEODATABASE_FILE from $(SourceDataset_GEODATABASE_FILE_4)

Writers:
- NULL_2: NULL
- GEODATABASE_FILE_4: GEODATABASE_FILE to $(DestDataset_GEODATABASE_FILE)

UCPOTENC (reader GEODATABASE_FILE_2)
    attributes: OBJECTID integer, UNID_CARTO integer, CANA_AZUCA char(8000), BANANO char(8000), AGRICOLA char(8000), INGENIERIA char(8000)
    -> FeatureMerger [SUPPLIER]
mapa_suelo_regven (reader GEODATABASE_FILE_1)
    attributes: OBJECTID integer, MIFCODE char(50), MSLINK double, MAPID double, SUPERFICIE double, SUELOA_ID double, UNID_CARTO char(50), SUPERF_HA double, IDENTIFICA char(50), Shape_Length double, Shape_Area double
    -> FeatureMerger [REQUESTOR]
FeatureMerger
    ATTR_ACCUM_MODE = Merge Supplier
    ATTR_CONFLICT_RES = Use Requestor
    IGNORE_NULLS = No
    JOIN_KEYS = @Value(UNID_CARTO) @Value(UNID_CARTO) STRING
    MERGE_TYPE = Attributes Only
    PROCESS_DUPS = NO
    REJECT_NULL_MISSING_KEYS = No
    SUPPLIERS_FIRST = No
    MERGED -> FeatureMerger_2 [REQUESTOR]
UCATRIBU (reader GEODATABASE_FILE_3)
    attributes: OBJECTID integer, UNID_CARTO char(5), TEXT_25CM char(68), TEXT_100CM char(68), PEDREGOSID char(38), GRAVA char(20), CAPA_LIMIT char(30), PROFUNDIDA char(40), CALCAREA char(50), INUNDACION char(45), SALINIDAD char(35), SODICIDAD char(25), REACCION char(30), PENDIENTE char(30), DRENAJE char(30)
    -> FeatureMerger_2 [SUPPLIER]
FeatureMerger_2
    ATTR_ACCUM_MODE = Merge Supplier
    ATTR_CONFLICT_RES = Use Requestor
    IGNORE_NULLS = No
    JOIN_KEYS = @Value(UNID_CARTO) @Value(UNID_CARTO) STRING
    MERGE_TYPE = Attributes Only
    PROCESS_DUPS = NO
    REJECT_NULL_MISSING_KEYS = No
    SUPPLIERS_FIRST = No
    MERGED -> AttributeManager
AttributeManager
    ATTR_TABLE:
      REMOVE Shape_Length
      REMOVE Shape_Area
      REMOVE fme_feature_type
      REMOVE BANANO
      REMOVE TEXT_25CM
      REMOVE TEXT_100CM
      REMOVE PEDREGOSID
      REMOVE GRAVA
      REMOVE CAPA_LIMIT
      REMOVE PROFUNDIDA
      REMOVE CALCAREA
      REMOVE REACCION
    -> mapasuelos_attr_poten (writer GEODATABASE_FILE_4)
mapasuelos_attr_poten (writer GEODATABASE_FILE_4)
    attributes: OBJECTID integer, MIFCODE char(50), MSLINK double, MAPID double, SUPERFICIE double, SUELOA_ID integer, UNID_CARTO integer, SUPERF_HA double, IDENTIFICA char(50), CANA_AZUCA char(8000), AGRICOLA char(8000), INGENIERIA char(8000), INUNDACION char(45), SALINIDAD char(35), SODICIDAD char(25), PENDIENTE char(30), DRENAJE char(30)
